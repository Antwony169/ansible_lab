ADTRAN-MEF-PER-NNI-TOTAL-COUNT-MIB DEFINITIONS ::= BEGIN

IMPORTS
   MODULE-IDENTITY,
   OBJECT-TYPE,
   Integer32
      FROM SNMPv2-SMI
   ifIndex  
       FROM IF-MIB
   HCPerfTimeElapsed,
   HCPerfValidIntervals,
   HCPerfInvalidIntervals,
   HCPerfCurrentCount,
   HCPerfIntervalCount,
   HCPerfTotalCount
      FROM HC-PerfHist-TC-MIB
   MODULE-COMPLIANCE,
   OBJECT-GROUP
      FROM SNMPv2-CONF
   adIdentity
      FROM ADTRAN-MIB
   adGenAOSMef,
   adGenAOSConformance
      FROM ADTRAN-AOS;

adGenAosMefPerNniTotalCountMib MODULE-IDENTITY
   LAST-UPDATED "202103140000Z" -- March 14, 2021
   ORGANIZATION "ADTRAN Inc."
   CONTACT-INFO
     "Info:   www.adtran.com
      Postal: ADTRAN, Inc.
              901 Explorer Blvd.
              Huntsville, AL 35806
      Tel:    +1 888 423-8726
      E-mail: support@adtran.com"

   DESCRIPTION
     "This MIB module defines high capacity total number of green, yellow, and red 
      counters statistics per NNI within an AOS product.

      Copyright (C) ADTRAN, Inc. (2017)."

   REVISION    "202103140000Z" -- March 14, 2021
   DESCRIPTION
     "Initial version"
    ::= { adIdentity 10000 53 9 11 }

adGenAosMefPerNniTotalCount OBJECT IDENTIFIER ::= { adGenAOSMef 11}

------------------------------------------------------------
-- Total number of counters for ingress,egress, yellow, and red counters,.
--
adMefPerNniTcTable OBJECT-TYPE
   SYNTAX      SEQUENCE OF AdMefPerNniTcEntry
   MAX-ACCESS  not-accessible
   STATUS      current
   DESCRIPTION
     "This table contains total number for ingress,egress, yellow, and red counters. This table is indexed by ifindex."
   ::= { adGenAosMefPerNniTotalCount 1 }

adMefPerNniTcEntry OBJECT-TYPE
   SYNTAX      AdMefPerNniTcEntry
   MAX-ACCESS  not-accessible
   STATUS      current
   DESCRIPTION
     "This specifies the information contained in one entry of the
      adMefPerNniTcTable. It is indexed by an interface's ifIndex."
   INDEX { ifIndex }
   ::= { adMefPerNniTcTable 1 }

AdMefPerNniTcEntry ::=
   SEQUENCE
   {
     
      adMefPerNniTotalIngressOctets                    HCPerfCurrentCount,
      adMefPerNniTotalEgressOctets                     HCPerfCurrentCount
   } 

adMefPerNniTotalIngressOctets OBJECT-TYPE
   SYNTAX      HCPerfCurrentCount
   MAX-ACCESS  read-only
   STATUS      current
   DESCRIPTION
     "Total number of ingress octets."
   ::= { adMefPerNniTcEntry 1 }


adMefPerNniTotalEgressOctets OBJECT-TYPE
   SYNTAX      HCPerfCurrentCount
   MAX-ACCESS  read-only
   STATUS      current
   DESCRIPTION
     "Total number of egress octets."
   ::= { adMefPerNniTcEntry 2 }


------------------------------------------------------------
-- Conformance information
--
adGenAosMefPerNniTotalCountConformance OBJECT IDENTIFIER
   ::= { adGenAOSConformance 36 }

adMefPerNniTotalCountGroups OBJECT IDENTIFIER
   ::= { adGenAosMefPerNniTotalCountConformance 1 }

adGenAosMefPerNniTotalCountCompliances OBJECT IDENTIFIER
   ::= { adGenAosMefPerNniTotalCountConformance 2 }

-- Compliance statements
--

adGenAosMefPerNniTotalCountCompliance MODULE-COMPLIANCE
   STATUS  current
   DESCRIPTION
     "The compliance statement for SNMPv2 entities which
      implement Nni interface for total number of count."
   MODULE
   MANDATORY-GROUPS {
      adMefPerNniTotalCountGroup
   }
   ::= { adGenAosMefPerNniTotalCountCompliances 1 }

-- Nnits of conformance
--
adMefPerNniTotalCountGroup OBJECT-GROUP
   OBJECTS 
   {
      adMefPerNniTotalIngressOctets,
      adMefPerNniTotalEgressOctets
   }
   STATUS  current
   DESCRIPTION
     "The Current Group."
   ::= { adMefPerNniTotalCountGroups 1 }

END
