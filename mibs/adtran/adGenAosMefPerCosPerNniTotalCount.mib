ADTRAN-MEF-PER-COS-PER-NNI-TOTAL-COUNT-MIB DEFINITIONS ::= BEGIN

IMPORTS
   MODULE-IDENTITY,
   OBJECT-TYPE,
   Integer32, Unsigned32
      FROM SNMPv2-SMI
   DisplayString
       FROM SNMPv2-TC
   ifIndex
       FROM IF-MIB
   HCPerfTimeElapsed,
   HCPerfValidIntervals,
   HCPerfInvalidIntervals,
   HCPerfCurrentCount,
   HCPerfIntervalCount,
   HCPerfTotalCount
      FROM HC-PerfHist-TC-MIB
   MODULE-COMPLIANCE,
   OBJECT-GROUP
      FROM SNMPv2-CONF
   adIdentity
      FROM ADTRAN-MIB
   adGenAOSMef,
   adGenAOSConformance
      FROM ADTRAN-AOS;

adGenAosMefPerCosPerNniTotalCountMib MODULE-IDENTITY
   LAST-UPDATED "202103140000Z" -- March 14, 2021
   ORGANIZATION "ADTRAN Inc."
   CONTACT-INFO
     "Info:   www.adtran.com
      Postal: ADTRAN, Inc.
              901 Explorer Blvd.
              Huntsville, AL 35806
      Tel:    +1 888 423-8726
      E-mail: support@adtran.com"

   DESCRIPTION
     "This MIB module defines high capacity performance statistics
      per COS per Nni within an AOS product.

      Copyright (C) ADTRAN, Inc. (2017)."

   REVISION    "202103140000Z" -- March 14, 2021
   DESCRIPTION
     "Initial version"
    ::= { adIdentity 10000 53 9 12 }

adGenAosMefPerCosPerNniTotalCount OBJECT IDENTIFIER ::= { adGenAOSMef 12}

------------------------------------------------------------
-- Current Table for Total count of Ingress, Egress, Ingress yellow discards and ingress red counters for Per Cos Per Nni. 
--
adMefPerCosPerNniTcTable OBJECT-TYPE
   SYNTAX      SEQUENCE OF AdMefPerCosPerNniTcEntry
   MAX-ACCESS  not-accessible
   STATUS      current
   DESCRIPTION
     "This table contains totla number of count for green, yellow and red 
      counters with Per Cos Per Nni. This table is indexed by ifIndex 
      and the queue number."
   ::= { adGenAosMefPerCosPerNniTotalCount 1 }

adMefPerCosPerNniTcEntry OBJECT-TYPE
   SYNTAX      AdMefPerCosPerNniTcEntry
   MAX-ACCESS  not-accessible
   STATUS      current
   DESCRIPTION
     "This specifies the information contained in one entry of the
      adMefPerCosPerNniTcTable. It is indexed by an interface's ifIndex,
      and the queue number."
   INDEX { ifIndex, adMefPerCosPerNniTcQueueNumber }
   ::= { adMefPerCosPerNniTcTable 1 }

AdMefPerCosPerNniTcEntry ::=
   SEQUENCE
   {
       adMefPerCosPerNniTcQueueNumber                         Unsigned32,
       adMefPerCosPerNniTotalEgressOctets                     HCPerfCurrentCount,
       adMefPerCosPerNniTotalIngressOctets                    HCPerfCurrentCount
   }

adMefPerCosPerNniTcQueueNumber OBJECT-TYPE
   SYNTAX      Unsigned32 (0..7)
   MAX-ACCESS  not-accessible
   STATUS      current
   DESCRIPTION
     "Nni queue number."
   ::= { adMefPerCosPerNniTcEntry 1 }
   

adMefPerCosPerNniTotalEgressOctets OBJECT-TYPE
   SYNTAX      HCPerfCurrentCount
   MAX-ACCESS  read-only
   STATUS      current
   DESCRIPTION
     "Total number of egress octets."
   ::= { adMefPerCosPerNniTcEntry 2 }


adMefPerCosPerNniTotalIngressOctets OBJECT-TYPE
   SYNTAX      HCPerfCurrentCount
   MAX-ACCESS  read-only
   STATUS      current
   DESCRIPTION
     "Total number of ingress octets."
   ::= { adMefPerCosPerNniTcEntry 3 }

------------------------------------------------------------
-- Conformance information
--
adGenAosMefPerCosPerNniTotalCountConformance OBJECT IDENTIFIER
   ::= { adGenAOSConformance 32 }

adMefPerCosPerNniTotalCountGroups OBJECT IDENTIFIER
   ::= { adGenAosMefPerCosPerNniTotalCountConformance 1 }

adGenAosMefPerCosPerNniTotalCountCompliances OBJECT IDENTIFIER
   ::= { adGenAosMefPerCosPerNniTotalCountConformance 2 }

-- Compliance statements
--

adGenAosMefPerNniTotalCountCompliance MODULE-COMPLIANCE
   STATUS  current
   DESCRIPTION
     "The compliance statement for SNMPv2 entities which
      implement Nni interface for total number of count."
   MODULE
   MANDATORY-GROUPS {
      adMefPerCosPerNniTotalCountGroup
   }
   ::= { adGenAosMefPerCosPerNniTotalCountCompliances 1 }

-- Nnits of conformance
--
adMefPerCosPerNniTotalCountGroup OBJECT-GROUP
   OBJECTS 
   {
      
      adMefPerCosPerNniTotalEgressOctets,
      adMefPerCosPerNniTotalIngressOctets
   }
   STATUS  current
   DESCRIPTION
     "The Current Group."
   ::= { adMefPerCosPerNniTotalCountGroups 1 }
END
