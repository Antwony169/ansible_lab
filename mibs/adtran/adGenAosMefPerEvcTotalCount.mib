ADTRAN-MEF-PER-EVC-TOTAL-COUNT-MIB DEFINITIONS ::= BEGIN

IMPORTS
   MODULE-IDENTITY,
   OBJECT-TYPE,
   Integer32
      FROM SNMPv2-SMI
   DisplayString
       FROM SNMPv2-TC
   HCPerfTimeElapsed,
   HCPerfValidIntervals,
   HCPerfInvalidIntervals,
   HCPerfCurrentCount,
   HCPerfIntervalCount,
   HCPerfTotalCount
      FROM HC-PerfHist-TC-MIB
   MODULE-COMPLIANCE,
   OBJECT-GROUP
      FROM SNMPv2-CONF
   adIdentity
      FROM ADTRAN-MIB
   adGenAOSMef,
   adGenAOSConformance
      FROM ADTRAN-AOS;

adGenAosMefPerEvcTotalCountMib MODULE-IDENTITY
   LAST-UPDATED "201710140000Z" -- October 14, 2017
   ORGANIZATION "ADTRAN Inc."
   CONTACT-INFO
     "Info:   www.adtran.com
      Postal: ADTRAN, Inc.
              901 Explorer Blvd.
              Huntsville, AL 35806
      Tel:    +1 888 423-8726
      E-mail: support@adtran.com"

   DESCRIPTION
     "This MIB module defines high capacity total number count for gree,yellow and red counters statistics
      per EVC within an AOS product.

      Copyright (C) ADTRAN, Inc. (2017)."

   REVISION    "201710140000Z" -- October  14, 2017
   DESCRIPTION
     "Initial version"
   REVISION    "202103140000Z" -- March 14, 2021
   DESCRIPTION
     "Added  adMefPerEvcTotalIngressOctets,adMefPerEvcTotalEgressOctets,adMefPerEvcTotalIngressYellowDiscardOctets,adMefPerEvcTotalIngressRedOctets 
      mib objects."
    ::= { adIdentity 10000 53 9 7 }

adGenAosMefPerEvcTotalCount OBJECT IDENTIFIER ::= { adGenAOSMef 7 }

------------------------------------------------------------
-- Current Table for Interface Total number of count.
--
adMefPerEvcTcTable OBJECT-TYPE
   SYNTAX      SEQUENCE OF AdMefPerEvcTcEntry
   MAX-ACCESS  not-accessible
   STATUS      current
   DESCRIPTION
     "This table contains total count for gree,yellow and red counters for frames and octotes.  
      This table is indexed by adMefPerEvcTcEvcNameFixedLen."
   ::= { adGenAosMefPerEvcTotalCount 1 }

adMefPerEvcTcEntry OBJECT-TYPE
   SYNTAX      AdMefPerEvcTcEntry
   MAX-ACCESS  not-accessible
   STATUS      current
   DESCRIPTION
     "This specifies the information contained in one entry of the
      adMefPerEvcTcTable.  It is indexed by an EVC's adMefPerEvcTcEvcNameFixedLen."
   INDEX { adMefPerEvcTcEvcNameFixedLen }
   ::= { adMefPerEvcTcTable 1 }

AdMefPerEvcTcEntry ::=
   SEQUENCE
   {
      adMefPerEvcTcEvcNameFixedLen                     OCTET STRING,
      adMefPerEvcTotalIngressGreenOctets               HCPerfCurrentCount,
      adMefPerEvcTotalIngressGreenFrames               HCPerfCurrentCount,
      adMefPerEvcTotalIngressYellowOctets              HCPerfCurrentCount,
      adMefPerEvcTotalIngressYellowFrames              HCPerfCurrentCount,
      adMefPerEvcTotalIngressRedFrames                 HCPerfCurrentCount,
      adMefPerEvcTotalIngressOctets                    HCPerfCurrentCount,
      adMefPerEvcTotalEgressOctets                     HCPerfCurrentCount,
      adMefPerEvcTotalIngressYellowDiscardOctets       HCPerfCurrentCount,
      adMefPerEvcTotalIngressRedOctets                 HCPerfCurrentCount

   } 

adMefPerEvcTcEvcNameFixedLen OBJECT-TYPE
   SYNTAX      OCTET STRING (SIZE (50))
   MAX-ACCESS  not-accessible
   STATUS      current
   DESCRIPTION
     "The name of the EVC.  This string is padded at the end with 0x00 so that 
      this table index has a fixed length of characters of the specified SIZE."
   ::= { adMefPerEvcTcEntry 1}

adMefPerEvcTotalIngressGreenOctets OBJECT-TYPE
   SYNTAX      HCPerfCurrentCount
   MAX-ACCESS  read-only
   STATUS      current
   DESCRIPTION
     "Total Green Octets"
   ::= { adMefPerEvcTcEntry 2 }

adMefPerEvcTotalIngressGreenFrames OBJECT-TYPE
   SYNTAX      HCPerfCurrentCount
   MAX-ACCESS  read-only
   STATUS      current
   DESCRIPTION
     "Total Green counter frames"
   ::= { adMefPerEvcTcEntry 3 }

adMefPerEvcTotalIngressYellowOctets OBJECT-TYPE
   SYNTAX      HCPerfCurrentCount
   MAX-ACCESS  read-only
   STATUS      current
   DESCRIPTION
     "Total Number of Yellow octets."
   ::= { adMefPerEvcTcEntry 4 }

adMefPerEvcTotalIngressYellowFrames OBJECT-TYPE
   SYNTAX      HCPerfCurrentCount
   MAX-ACCESS  read-only
   STATUS      current
   DESCRIPTION
     "The total number of yellow frames."
   ::= { adMefPerEvcTcEntry 5 }

adMefPerEvcTotalIngressRedFrames OBJECT-TYPE
   SYNTAX      HCPerfCurrentCount
   MAX-ACCESS  read-only
   STATUS      current
   DESCRIPTION
     "Total number of red frames."
   ::= { adMefPerEvcTcEntry 6 }


adMefPerEvcTotalIngressOctets OBJECT-TYPE
   SYNTAX      HCPerfCurrentCount
   MAX-ACCESS  read-only
   STATUS      current
   DESCRIPTION
     "Total number of ingress octets."
   ::= { adMefPerEvcTcEntry 7 }


adMefPerEvcTotalEgressOctets OBJECT-TYPE
   SYNTAX      HCPerfCurrentCount
   MAX-ACCESS  read-only
   STATUS      current
   DESCRIPTION
     "Total number of egress octets."
   ::= { adMefPerEvcTcEntry 8 }


adMefPerEvcTotalIngressYellowDiscardOctets OBJECT-TYPE
   SYNTAX      HCPerfCurrentCount
   MAX-ACCESS  read-only
   STATUS      current
   DESCRIPTION
     "Total number of ingress  yellow discard octets."
   ::= { adMefPerEvcTcEntry 9 }

adMefPerEvcTotalIngressRedOctets OBJECT-TYPE
   SYNTAX      HCPerfCurrentCount
   MAX-ACCESS  read-only
   STATUS      current
   DESCRIPTION
     "Total number of ingress  red octets."
   ::= { adMefPerEvcTcEntry 10 }

 ------------------------------------------------------------
-- Conformance information
--
adGenAosMefPerEvcTotalCountConformance OBJECT IDENTIFIER
   ::= { adGenAOSConformance 29 }

adMefPerEvcTotalCountGroups OBJECT IDENTIFIER
   ::= { adGenAosMefPerEvcTotalCountConformance 1 }

adGenAosMefPerEvcTotalCountCompliances OBJECT IDENTIFIER
   ::= { adGenAosMefPerEvcTotalCountConformance 2 }

-- Compliance statements
--

adGenAosMefPerEvcTotalCountCompliance MODULE-COMPLIANCE
   STATUS  current
   DESCRIPTION
     "The compliance statement for SNMPv2 entities which
      implement total count of EVC for green,yellow and red counters."
   MODULE
   MANDATORY-GROUPS {
      adMefPerEvcTotalCountGroup
   }
   ::= { adGenAosMefPerEvcTotalCountCompliances 1 }

-- Units of conformance
--
adMefPerEvcTotalCountGroup OBJECT-GROUP
   OBJECTS 
   {
      adMefPerEvcTotalIngressGreenOctets,
      adMefPerEvcTotalIngressGreenFrames,      
      adMefPerEvcTotalIngressYellowOctets,
      adMefPerEvcTotalIngressYellowFrames,	  
      adMefPerEvcTotalIngressRedFrames,
      adMefPerEvcTotalIngressOctets,                    
      adMefPerEvcTotalEgressOctets,
      adMefPerEvcTotalIngressYellowDiscardOctets,
      adMefPerEvcTotalIngressRedOctets                 
   }
   STATUS  current
   DESCRIPTION
     "The 1 day interval group."
   ::= { adMefPerEvcTotalCountGroups 1 }   
END
