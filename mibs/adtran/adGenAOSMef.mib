ADTRAN-AOS-MEF-MIB DEFINITIONS ::= BEGIN

       IMPORTS
           MODULE-IDENTITY
               FROM SNMPv2-SMI
           adShared, adIdentityShared
               FROM ADTRAN-MIB
          adGenAOS, adGenAOSMef
               FROM ADTRAN-AOS;

       adGenAOSMefMib MODULE-IDENTITY
        LAST-UPDATED "201409100000Z" -- September 10, 2014
	ORGANIZATION "ADTRAN, Inc."
        CONTACT-INFO
               "Technical Support Dept.
                Postal: ADTRAN, Inc.
                901 Explorer Blvd.
                Huntsville, AL 35806

                Tel: +1 800 726-8663
                Fax: +1 256 963 6217
                E-mail: support@adtran.com"

            DESCRIPTION
                        "This MIB defines the Adtran OS Common enterprise tree node.  It
                         provides a basis for the definition of all other Adtran OS MEF
                         MIBs."

            REVISION    "201409100000Z" -- September 10, 2014
            DESCRIPTION
                    "Initial version of this MIB module."

             REVISION   "202103140000Z" -- March 14, 2021 
            DESCRIPTION
                    "Added adGenAosMefPerNniTotalCountMib,adGenAosMefPerCosPerNniTotalCountMib MIB modules."

           ::= { adGenAOS 9 }

          adGenAosMefPerUniPerfHistoryMib         OBJECT IDENTIFIER ::= { adGenAOSMef 1 }
          adGenAosMefPerCosPerUniPerfHistoryMib   OBJECT IDENTIFIER ::= { adGenAOSMef 2 }
          adGenAosMefPerEvcPerfHistoryMib         OBJECT IDENTIFIER ::= { adGenAOSMef 3 }
          adGenAosMefPerCosPerEvcPerfHistoryMib   OBJECT IDENTIFIER ::= { adGenAOSMef 4 }
          adGenAosMefPerUniTotalCountMib          OBJECT IDENTIFIER ::= { adGenAOSMef 5 }
          adGenAosMefPerCosPerUniTotalCountMib    OBJECT IDENTIFIER ::= { adGenAOSMef 6 }
          adGenAosMefPerEvcTotalCountMib          OBJECT IDENTIFIER ::= { adGenAOSMef 7 }
          adGenAosMefPerCosPerEvcTotalCountMib    OBJECT IDENTIFIER ::= { adGenAOSMef 8 }
          adGenAosY1731Mib                        OBJECT IDENTIFIER ::= { adGenAOSMef 9 }
          adGenAosEthLpbkMib                      OBJECT IDENTIFIER ::= { adGenAOSMef 10 }
          adGenAosMefPerNniTotalCountMib          OBJECT IDENTIFIER ::= { adGenAOSMef 11 }
          adGenAosMefPerCosPerNniTotalCountMib    OBJECT IDENTIFIER ::= { adGenAOSMef 12 }

    --
    -- adGenAOS
    --
    -- The features in Adtran OS products that support SNMP
    -- management appear in a list under the "adGenAOS" node.
    --

    --
    -- AOS Common Section - adGenAOSMef
    --
    -- Contains MEF information and config for AOS products
    -- identifier sequence - 1.3.6.1.4.1.664.5.53.9
    --

    --
    -- AOS Common Section - adGenAosMefPerUniPerfHistoryMib
    --
    -- Contains performance history information for UNI interfaces.
    -- identifier sequence - 1.3.6.1.4.1.664.5.53.9.1
    --
    --

    --
    -- AOS Common Section - adGenAosMefPerCosPerUniPerfHistoryMib
    --
    -- Contains performance history information for UNI interfaces per queue number.
    -- identifier sequence - 1.3.6.1.4.1.664.5.53.9.2
    --
    --

    --
    -- AOS Common Section - adGenAosMefPerEvcPerfHistoryMib
    --
    -- Contains performance history information for EVCs.
    -- identifier sequence - 1.3.6.1.4.1.664.5.53.9.3
    --
    --

    --
    -- AOS Common Section - adGenAosMefPerCosPerEvcPerfHistoryMib
    --
    -- Contains performance history information for EVCs per queue number.
    -- identifier sequence - 1.3.6.1.4.1.664.5.53.9.4
    --
    --

    --
    -- AOS Common Section - adGenAosMefPerUniTotalCountMib
    --
    -- Contains total information for UNI interfaces.
    -- identifier sequence - 1.3.6.1.4.1.664.5.53.9.5
    --
    --
    
    --
    -- AOS Common Section - adGenAosMefPerCosPerUniTotalCountMib
    -- 
    -- Contains total count information for UNI interfaces per queue number.
    -- identifier sequence - 1.3.6.1.4.1.664.5.53.9.6
    --
    --

    --
    -- AOS Common Section - adGenAosMefPerEvcTotalCountMib
    -- 
    -- Contains total count information for EVCs.
    -- identifier sequence - 1.3.6.1.4.1.664.5.53.9.7
    --
    --

    --
    -- AOS Common Section - adGenAosMefPerCosPerEvcTotalCountMib 
    -- 
    -- Contains total count information for EVCs per queue number.
    -- identifier sequence - 1.3.6.1.4.1.664.5.53.9.8
    --
    --

    --
    -- AOS Common Section - adGenAosY1731Mib 
    -- 
    -- Contains alarms information for local MEP for Y1731 implemnetation.
    -- identifier sequence - 1.3.6.1.4.1.664.5.53.9.9
    --
    --
    
    --
    -- AOS Common Section - adGenAOSEthLpbkMib
    --
    -- Contains Ethernet Loopback Terminal/Facility Details.
    -- identifier sequence - 1.3.6.1.4.1.664.5.53.9.10
    --
    --

    --
    -- AOS Common Section - adGenAosMefPerrNniTotalCountMib
    --
    -- Contains total information for NNI interfaces.
    -- identifier sequence - 1.3.6.1.4.1.664.5.53.9.11
    --
    --

    --
    -- AOS Common Section - adGenAosMefPerCosPerNniTotalCountMib
    -- 
    -- Contains total count information for NNI interfaces per queue number.
    -- identifier sequence - 1.3.6.1.4.1.664.5.53.9.12
    --
    --



       END
