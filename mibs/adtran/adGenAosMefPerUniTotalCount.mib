ADTRAN-MEF-PER-UNI-TOTAL-COUNT-MIB DEFINITIONS ::= BEGIN

IMPORTS
   MODULE-IDENTITY,
   OBJECT-TYPE,
   Integer32
      FROM SNMPv2-SMI
   ifIndex  
       FROM IF-MIB
   HCPerfTimeElapsed,
   HCPerfValidIntervals,
   HCPerfInvalidIntervals,
   HCPerfCurrentCount,
   HCPerfIntervalCount,
   HCPerfTotalCount
      FROM HC-PerfHist-TC-MIB
   MODULE-COMPLIANCE,
   OBJECT-GROUP
      FROM SNMPv2-CONF
   adIdentity
      FROM ADTRAN-MIB
   adGenAOSMef,
   adGenAOSConformance
      FROM ADTRAN-AOS;

adGenAosMefPerUniTotalCountMib MODULE-IDENTITY
   LAST-UPDATED "201710140000Z" -- October 14, 2017
   ORGANIZATION "ADTRAN Inc."
   CONTACT-INFO
     "Info:   www.adtran.com
      Postal: ADTRAN, Inc.
              901 Explorer Blvd.
              Huntsville, AL 35806
      Tel:    +1 888 423-8726
      E-mail: support@adtran.com"

   DESCRIPTION
     "This MIB module defines high capacity total number of green, yellow, and red 
      counters statistics per UNI within an AOS product.

      Copyright (C) ADTRAN, Inc. (2017)."

   REVISION    "201710140000Z" -- October 14, 2017
   DESCRIPTION
     "Initial version"
   REVISION    "202103140000Z" -- March 14, 2021
   DESCRIPTION
     "Added  adMefPerUniTotalIngressOctets,adMefPerUniTotalEgressOctets,adMefPerUniTotalIngressYellowDiscardOctets,adMefPerUniTotalIngressRedOctets 
      mib objects."
    ::= { adIdentity 10000 53 9 5 }

adGenAosMefPerUniTotalCount OBJECT IDENTIFIER ::= { adGenAOSMef 5 }

------------------------------------------------------------
-- Total number of counters for green, yellow, and red counters,.
--
adMefPerUniTcTable OBJECT-TYPE
   SYNTAX      SEQUENCE OF AdMefPerUniTcEntry
   MAX-ACCESS  not-accessible
   STATUS      current
   DESCRIPTION
     "This table contains total number for green, yellow, and red counters. This table is indexed by ifindex."
   ::= { adGenAosMefPerUniTotalCount 1 }

adMefPerUniTcEntry OBJECT-TYPE
   SYNTAX      AdMefPerUniTcEntry
   MAX-ACCESS  not-accessible
   STATUS      current
   DESCRIPTION
     "This specifies the information contained in one entry of the
      adMefPerUniTcTable. It is indexed by an interface's ifIndex."
   INDEX { ifIndex }
   ::= { adMefPerUniTcTable 1 }

AdMefPerUniTcEntry ::=
   SEQUENCE
   {
      adMefPerUniTotalIngressGreenOctets               HCPerfCurrentCount,
      adMefPerUniTotalIngressGreenFrames               HCPerfCurrentCount,
      adMefPerUniTotalIngressYellowOctets              HCPerfCurrentCount,
      adMefPerUniTotalIngressYellowFrames              HCPerfCurrentCount,
      adMefPerUniTotalIngressRedFrames                 HCPerfCurrentCount,
      adMefPerUniTotalIngressOctets                    HCPerfCurrentCount,
      adMefPerUniTotalEgressOctets                    HCPerfCurrentCount,
      adMefPerUniTotalIngressYellowDiscardOctets       HCPerfCurrentCount,
      adMefPerUniTotalIngressRedOctets                 HCPerfCurrentCount
   } 

adMefPerUniTotalIngressGreenOctets OBJECT-TYPE
   SYNTAX      HCPerfCurrentCount
   MAX-ACCESS  read-only
   STATUS      current
   DESCRIPTION
     "Total number of Green Octets"
   ::= { adMefPerUniTcEntry 1 }

adMefPerUniTotalIngressGreenFrames OBJECT-TYPE
   SYNTAX      HCPerfCurrentCount
   MAX-ACCESS  read-only
   STATUS      current
   DESCRIPTION
     "Total number of Green frames."
   ::= { adMefPerUniTcEntry 2 }

adMefPerUniTotalIngressYellowOctets OBJECT-TYPE
   SYNTAX      HCPerfCurrentCount
   MAX-ACCESS  read-only
   STATUS      current
   DESCRIPTION
     "Total number of yellow octets."
   ::= { adMefPerUniTcEntry 3 }

adMefPerUniTotalIngressYellowFrames OBJECT-TYPE
   SYNTAX      HCPerfCurrentCount
   MAX-ACCESS  read-only
   STATUS      current
   DESCRIPTION
     "The total number of yellow frames."
   ::= { adMefPerUniTcEntry 4 }

adMefPerUniTotalIngressRedFrames OBJECT-TYPE
   SYNTAX      HCPerfCurrentCount
   MAX-ACCESS  read-only
   STATUS      current
   DESCRIPTION
     "Total number of red frames."
   ::= { adMefPerUniTcEntry 5 }

adMefPerUniTotalEgressOctets OBJECT-TYPE
   SYNTAX      HCPerfCurrentCount
   MAX-ACCESS  read-only
   STATUS      current
   DESCRIPTION
     "Total number of egress octets."
   ::= { adMefPerUniTcEntry 6 }


adMefPerUniTotalIngressOctets OBJECT-TYPE
   SYNTAX      HCPerfCurrentCount
   MAX-ACCESS  read-only
   STATUS      current
   DESCRIPTION
     "Total number of ingress octets."
   ::= { adMefPerUniTcEntry 7 }


adMefPerUniTotalIngressYellowDiscardOctets OBJECT-TYPE
   SYNTAX      HCPerfCurrentCount
   MAX-ACCESS  read-only
   STATUS      current
   DESCRIPTION
     "Total number of ingress  yellow discard octets."
   ::= { adMefPerUniTcEntry 8 }

adMefPerUniTotalIngressRedOctets OBJECT-TYPE
   SYNTAX      HCPerfCurrentCount
   MAX-ACCESS  read-only
   STATUS      current
   DESCRIPTION
     "Total number of ingress  red octets."
   ::= { adMefPerUniTcEntry 9 }



------------------------------------------------------------
-- Conformance information
--
adGenAosMefPerUniTotalCountConformance OBJECT IDENTIFIER
   ::= { adGenAOSConformance 27 }

adMefPerUniTotalCountGroups OBJECT IDENTIFIER
   ::= { adGenAosMefPerUniTotalCountConformance 1 }

adGenAosMefPerUniTotalCountCompliances OBJECT IDENTIFIER
   ::= { adGenAosMefPerUniTotalCountConformance 2 }

-- Compliance statements
--

adGenAosMefPerUniTotalCountCompliance MODULE-COMPLIANCE
   STATUS  current
   DESCRIPTION
     "The compliance statement for SNMPv2 entities which
      implement UNI interface for total number of count."
   MODULE
   MANDATORY-GROUPS {
      adMefPerUniTotalCountGroup
   }
   ::= { adGenAosMefPerUniTotalCountCompliances 1 }

-- Units of conformance
--
adMefPerUniTotalCountGroup OBJECT-GROUP
   OBJECTS 
   {
      adMefPerUniTotalIngressGreenOctets,
      adMefPerUniTotalIngressGreenFrames,      
      adMefPerUniTotalIngressYellowOctets,
      adMefPerUniTotalIngressYellowFrames,	  
      adMefPerUniTotalIngressRedFrames,
      adMefPerUniTotalEgressOctets,
      adMefPerUniTotalIngressOctets,
      adMefPerUniTotalIngressYellowDiscardOctets,
      adMefPerUniTotalIngressRedOctets

   }
   STATUS  current
   DESCRIPTION
     "The Current Group."
   ::= { adMefPerUniTotalCountGroups 1 }

END
